Attribute VB_Name = "PipeArgs"
Attribute VB_Base = "0{62F124D2-3A37-4424-A33C-0A197F25B284}{6F459F93-DDC6-47E3-ABEF-37ECC2E75375}"
Attribute VB_GlobalNameSpace = False
Attribute VB_Creatable = False
Attribute VB_PredeclaredId = True
Attribute VB_Exposed = False
Attribute VB_TemplateDerived = False
Attribute VB_Customizable = False
Dim asdf As Double

Private Sub CommandButton1_Click()
    PipeArgs.hide
End Sub

Private Sub UserForm_Activate()
End Sub

Attribute VB_Name = "ThisDrawing"
Attribute VB_Base = "0{0063BC47-A0C5-44BC-ACC3-50962CA5E9C2}"
Attribute VB_GlobalNameSpace = False
Attribute VB_Creatable = False
Attribute VB_PredeclaredId = True
Attribute VB_Exposed = True
Attribute VB_TemplateDerived = False
Attribute VB_Customizable = True

Sub make_pipe()
'diameter As Double, curve_radius As Double, thickness As Double
    On Error GoTo endfunc
        
    ' deal with arguments
    If PipeArgs.diameter = "" Then
        PipeArgs.diameter = "40"
        PipeArgs.radius = "30"
        PipeArgs.thickness = "2"
    End If
    PipeArgs.show
    
    Dim diameter As Double
    Dim radius As Double
    Dim thickness As String
    diameter = CDbl(PipeArgs.diameter.Text)
    radius = CDbl(PipeArgs.radius.Text)
    thickness = PipeArgs.thickness.Text
    
    Dim Selection As AcadSelectionSet
    'Dim Obj As AcadEntity
    Dim Bound As Double
    
    Dim Obj As Object
    Dim Pt As Variant
    Me.Utility.GetEntity Obj, Pt, "Select 3dPolyLine"
        
    If Obj Is Nothing Then
        GoTo endfunc
    End If
    
    'Makes a selectionset.
    'On Error Resume Next
    '   Set Selection = ThisDrawing.SelectionSets.Item("Select polyline.")
    'If Err Then
    '   Set Selection = ThisDrawing.SelectionSets.Add("Select polyline.")
    '   Err.Clear
    'Else
    '    Selection.Clear
    'End If
    
    'Select the polyline.
    'Selection.SelectOnScreen
    
    'For Each Obj In Selection
        If Not Obj.ObjectName = "AcDb3dPolyline" Then
            MsgBox "Object not a 3D PolyLine but a " & Obj.ObjectName
            GoTo endfunc
        End If
           
        Dim Poly As Acad3DPolyline
        Set Poly = Obj
                    
        Dim new_object_index As Integer
        new_object_index = ThisDrawing.ModelSpace.Count
        
        On Error GoTo cleanup
        
        'set up undo
        comString = "_UNDO" & vbCr _
                  & "Begin" & vbCr
        ThisDrawing.SendCommand comString
        
        'explode polyline
        lines = Poly.Explode
        
        'Fillet each line pair
        ThisDrawing.SetVariable "TRIMMODE", 1
        ThisDrawing.SetVariable "FILLETRAD", radius
        line_bounds = UBound(lines)
        For i = 0 To line_bounds - 1
            comString = "_FILLET" & vbCr _
                      & "(HANDENT " & Chr(34) & CStr(lines(i).Handle) & Chr(34) & ")" & vbCr & "(HANDENT " & Chr(34) & CStr(lines(i + 1).Handle) & Chr(34) & ")" & vbCr
            ThisDrawing.SendCommand comString
            If Not Err.Number = 0 Then
                MsgBox "Error occured during 'SendCommand'" & vbNewLine & Err.Description
                GoTo cleanup
            End If
        Next
        
        'join all of this into a new spline
        comString = "_JOIN" & vbCr
        For i = new_object_index To ThisDrawing.ModelSpace.Count - 1
            comString = comString & "(HANDENT " & Chr(34) & CStr(ThisDrawing.ModelSpace.Item(i).Handle) & Chr(34) & ")" & vbCr
        Next
        comString = comString & vbCr
        ThisDrawing.SendCommand comString
        If Not Err.Number = 0 Then
            MsgBox "Error occured during 'SendCommand'" & vbNewLine & Err.Description
            GoTo cleanup
        End If
                    
        'make it a pipe
        Dim acCircle As AcadCircle
        Dim centerPoint(0 To 2) As Double
        centerPoint(0) = 0#
        centerPoint(1) = 0#
        centerPoint(2) = 0#
        Set acCircle = ThisDrawing.ModelSpace.AddCircle(centerPoint, diameter / 2)
                    
        comString = "_SWEEP" & vbCr _
                  & "MOde SU" & vbCr _
                  & "(HANDENT " & Chr(34) & CStr(acCircle.Handle) & Chr(34) & ")" & vbCr _
                  & vbCr _
                  & "(HANDENT " & Chr(34) & CStr(ThisDrawing.ModelSpace.Item(new_object_index).Handle) & Chr(34) & ")" & vbCr
        ThisDrawing.SendCommand comString
        If Not Err.Number = 0 Then
            MsgBox "Error occured during 'SendCommand'" & vbNewLine & Err.Description
            GoTo cleanup
        End If
        
        'erase temp circle
        comString = "_ERASE" & vbCr _
                  & "(HANDENT " & Chr(34) & CStr(acCircle.Handle) & Chr(34) & ")" & vbCr _
                  & vbCr
        ThisDrawing.SendCommand comString
        If Not Err.Number = 0 Then
            MsgBox "Error occured during 'SendCommand'" & vbNewLine & Err.Description
            GoTo cleanup
        End If
        
        'erase temp spline
        comString = "_ERASE" & vbCr _
                  & "(HANDENT " & Chr(34) & CStr(ThisDrawing.ModelSpace.Item(new_object_index).Handle) & Chr(34) & ")" & vbCr _
                  & vbCr
        ThisDrawing.SendCommand comString
        If Not Err.Number = 0 Then
            MsgBox "Error occured during 'SendCommand'" & vbNewLine & Err.Description
            GoTo cleanup
        End If
        
        'thicken tube surface
        Dim asdf As AcadSweptSurface
        
        comString = "_THICKEN" & vbCr _
                  & "(HANDENT " & Chr(34) & CStr(ThisDrawing.ModelSpace.Item(new_object_index).Handle) & Chr(34) & ")" & vbCr _
                  & vbCr _
                  & thickness & vbCr
        ThisDrawing.SendCommand comString
        If Not Err.Number = 0 Then
            MsgBox "Error occured during 'SendCommand'" & vbNewLine & Err.Description
            GoTo cleanup
        End If

        ThisDrawing.EndUndoMark
        GoTo endfunc
        
cleanup:
        While ThisDrawing.ModelSpace.Count > new_object_index
            comString = "_ERASE" & vbCr _
                      & "(HANDENT " & Chr(34) & CStr(ThisDrawing.ModelSpace.Item(new_object_index).Handle) & Chr(34) & ")" & vbCr _
                      & vbCr
            ThisDrawing.SendCommand comString
            If Err.Number <> 0 Then
                MsgBox "Couldn't clean up due to error during 'SendCommand'" & vbNewLine & Err.Description
                GoTo endfunc
            End If
        Wend
        
    'Next Obj
endfunc:
End Sub
